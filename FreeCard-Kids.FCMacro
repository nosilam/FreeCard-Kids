# -*- coding: utf-8 -*-
"""
FreeCard Kids
Version 0.6

Erzeugt eine Visitenkarten-Basis.
FreeCAD 1.1.1
"""

# ------------------------------------------------------------
# Projektverzeichnis
# ------------------------------------------------------------

try:
    PROJECT_DIR = os.path.dirname(os.path.realpath(__file__))
except NameError:
    PROJECT_DIR = os.getcwd()

if PROJECT_DIR not in sys.path:
    sys.path.insert(0, PROJECT_DIR)

import FreeCAD as App
import Part
import Draft
import os
import subprocess
import sys

# Konfiguration laden
from config import (
    CARD_WIDTH,
    CARD_HEIGHT,
    FRAME_WIDTH,
    FRAME_HEIGHT,
    BASE_THICKNESS,
    RELIEF_HEIGHT,
    QR_SIZE,
    QR_MARGIN,
    QR_FILE,
    QR_OFFSET_X, 
    QR_OFFSET_Y,
    CHILD_NAME,
    MOM_PHONE,
    DAD_PHONE,
    FONT_NAME,
    FONT_FILE,
    FONT_SIZE_NAME,
    FONT_SIZE_PHONE,
    FONT_SIZE_INFO,
    INFO_DE,
    INFO_EN
)
#from create_vcard_qr_svg import create_qr
from vcard_qr_matrix import QR_MATRIX, QR_MODULES

def get_qr_module_size():

    return QR_SIZE / QR_MODULES
    
print("FreeCard Config geladen")
print("-----------------------")
print("Karte:", CARD_WIDTH, "x", CARD_HEIGHT)
print("QR:", QR_SIZE)
print("QR Rand:", QR_MARGIN)
print("Child:", CHILD_NAME)
print("Mama:", MOM_PHONE)
print("Papa:", DAD_PHONE)
print("QR-Module :", QR_MODULES)
print("Modulgröße:", get_qr_module_size())
print("Matrix Zeilen:", len(QR_MATRIX))
print("Matrix Spalten:", len(QR_MATRIX[0]))
# ------------------------------------------------------------
# Schrift konfigurieren
# ------------------------------------------------------------

def get_font_file():
    """Liefert den Pfad zur gewünschten Schriftdatei."""

    if FONT_FILE:
        if os.path.exists(FONT_FILE):
            return FONT_FILE
        raise RuntimeError(f"Schriftdatei nicht gefunden: {FONT_FILE}")

    try:
        path = subprocess.check_output(
            ["fc-match", "-f", "%{file}", FONT_NAME],
            text=True
        ).strip()

        if os.path.exists(path):
            return path

    except Exception as err:
        raise RuntimeError(
            f"Schrift '{FONT_NAME}' konnte nicht gefunden werden."
        ) from err

    raise RuntimeError("Keine passende Schrift gefunden.")

# ------------------------------------------------------------
# Text erzeugen
# ------------------------------------------------------------

def create_text(doc, text, size, y):

    font = get_font_file()

    txt = Draft.makeShapeString(
        String=text,
        FontFile=font,
        Size=size
    )

    doc.recompute()

    # Breite des Textes bestimmen
    bbox = txt.Shape.BoundBox

    # Text horizontal zentrieren
    x = (CARD_WIDTH - bbox.XLength) / 2

    txt.Placement.Base = App.Vector(
        x,
        y,
        BASE_THICKNESS + FRAME_HEIGHT
    )

    doc.recompute()

    return txt
        
# ------------------------------------------------------------
# Telefonnummer erzeugen
# ------------------------------------------------------------

def create_phone(doc, label, phone, y):

    text = f"{label}: {phone}"

    return create_text(
        doc,
        text,
        FONT_SIZE_PHONE,
        y
    )


# ------------------------------------------------------------
# Dokument holen oder erzeugen
# ------------------------------------------------------------

doc = App.ActiveDocument

if doc is None:
    doc = App.newDocument("FreeCard-Kids")

# ------------------------------------------------------------
# Alte FreeCard löschen
# ------------------------------------------------------------

for obj in list(doc.Objects):
    if obj.Name.startswith("FreeCard"):
        doc.removeObject(obj.Name)

doc.recompute()

# ------------------------------------------------------------
# Karte erzeugen
# ------------------------------------------------------------

shape = Part.makeBox(
    CARD_WIDTH,
    CARD_HEIGHT,
    BASE_THICKNESS
)

# Nur die vertikalen Kanten verrunden
vertical_edges = []

for edge in shape.Edges:

    v1 = edge.Vertexes[0].Point
    v2 = edge.Vertexes[1].Point

    if abs(v1.x - v2.x) < 0.001 \
       and abs(v1.y - v2.y) < 0.001:

        vertical_edges.append(edge)

shape = shape.makeFillet(
    5.0,
    vertical_edges
)

card = doc.addObject(
    "Part::Feature",
    "FreeCard"
)

# ------------------------------------------------------------
# Rahmen erzeugen
# ------------------------------------------------------------

inner = Part.makeBox(
    CARD_WIDTH - 2 * FRAME_WIDTH,
    CARD_HEIGHT - 2 * FRAME_WIDTH,
    FRAME_HEIGHT
)

inner.translate(
    App.Vector(
        FRAME_WIDTH,
        FRAME_WIDTH,
        BASE_THICKNESS
    )
)

outer = Part.makeBox(
    CARD_WIDTH,
    CARD_HEIGHT,
    FRAME_HEIGHT
)

outer.translate(
    App.Vector(
        0,
        0,
        BASE_THICKNESS
    )
)

# Gleiche Rundungen wie die Grundplatte
outer = outer.makeFillet(5.0, [
    e for e in outer.Edges
    if abs(e.Vertexes[0].Point.x - e.Vertexes[1].Point.x) < 0.001
    and abs(e.Vertexes[0].Point.y - e.Vertexes[1].Point.y) < 0.001
])

inner = inner.makeFillet(
    max(0.1, 5.0 - FRAME_WIDTH),
    [
        e for e in inner.Edges
        if abs(e.Vertexes[0].Point.x - e.Vertexes[1].Point.x) < 0.001
        and abs(e.Vertexes[0].Point.y - e.Vertexes[1].Point.y) < 0.001
    ]
)

frame = outer.cut(inner)

shape = shape.fuse(frame)

card.Shape = shape

# ------------------------------------------------------------
# Name
# ------------------------------------------------------------

name = create_text(
    doc,
    CHILD_NAME,
    FONT_SIZE_NAME,
    CARD_HEIGHT - 12
)

# ------------------------------------------------------------
# Telefonnummern
# ------------------------------------------------------------

mom = create_phone(
    doc,
    "Mama",
    MOM_PHONE,
    CARD_HEIGHT - 22
)

# ------------------------------------------------------------
# QR-Code erzeugen
# ------------------------------------------------------------

def create_qr():

    module_size = QR_SIZE / QR_MODULES

    qr_x = CARD_WIDTH - QR_SIZE - QR_OFFSET_X
    qr_y = (CARD_HEIGHT - QR_SIZE) / 2 + QR_OFFSET_Y
	
    faces = []
    
    for row, line in enumerate(QR_MATRIX):

        col = 0

        while col < QR_MODULES:

            if not line[col]:
                col += 1
                continue

            start = col

            while col < QR_MODULES and line[col]:
                col += 1

            length = col - start

            x1 = qr_x + start * module_size
            x2 = qr_x + (start + length) * module_size

            y1 = qr_y + (QR_MODULES - row - 1) * module_size
            y2 = y1 + module_size

            wire = Part.makePolygon([
                App.Vector(x1, y1, 0),
                App.Vector(x2, y1, 0),
                App.Vector(x2, y2, 0),
                App.Vector(x1, y2, 0),
                App.Vector(x1, y1, 0)
            ])

            faces.append(Part.Face(wire))

    print("QR-Flächen:", len(faces))

    if not faces:
        raise RuntimeError("QR-Code leer.")

    compound = Part.makeCompound(faces)

    qr = compound.extrude(
        App.Vector(
            0,
            0,
            RELIEF_HEIGHT
        )
    )

    qr.translate(
        App.Vector(
            0,
            0,
            BASE_THICKNESS
        )
    )

    return qr

# ------------------------------------------------------------
# QR-Position berechnen
# ------------------------------------------------------------

def get_qr_position():

    x = CARD_WIDTH - QR_SIZE - QR_MARGIN

    y = (CARD_HEIGHT - QR_SIZE) / 2

    return x, y

dad = create_phone(
    doc,
    "Papa",
    DAD_PHONE,
    CARD_HEIGHT - 29
)

# ------------------------------------------------------------
# Hinweis
# ------------------------------------------------------------

info_de = create_text(
    doc,
    INFO_DE,
    FONT_SIZE_INFO,
    8
)

info_en = create_text(
    doc,
    INFO_EN,
    FONT_SIZE_INFO,
    4
)

qr = create_qr()

shape = shape.fuse(qr)

card.Shape = shape

doc.recompute()

App.ActiveDocument.recompute()

print("FreeCard Version 0.6 erstellt.")
